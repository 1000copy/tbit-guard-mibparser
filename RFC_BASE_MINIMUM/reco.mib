--- reco first mib 
reco DEFINITIONS ::= BEGIN
    IMPORTS
        enterprises, IpAddress, Integer32, Unsigned32, Counter64, 
        OBJECT-TYPE         
            FROM SNMPv2-SMI;
    tbit OBJECT IDENTIFIER ::= { enterprises 66666 }
    RecoDevice OBJECT IDENTIFIER ::= { tbit 1 }
    RecoDevice1 OBJECT IDENTIFIER ::= { tbit 2 }
    Name OBJECT-TYPE
        SYNTAX OCTET STRING
        MAX-ACCESS read-write
        STATUS current
        DESCRIPTION
            "Description."
        ::= { RecoDevice 1 }
  
END
